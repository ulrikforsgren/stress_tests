module empty-template-service {
  namespace "http://com/example/emptytemplateservice";
  prefix empty-template-service;

  import ietf-inet-types {
    prefix inet;
  }
  import tailf-ncs {
    prefix ncs;
  }

  container empty-template-service {
    list service {
      key name;

      uses ncs:service-data;
      ncs:servicepoint "empty-template-service";

      leaf name {
        type string;
      }

      leaf str-value {
        type string;
      }
    }
  }
}
