module empty-service {
  namespace "http://com/example/emptyservice";
  prefix empty-service;

  import ietf-inet-types {
    prefix inet;
  }
  import tailf-ncs {
    prefix ncs;
  }

  container empty-service {
    list service {
      key name;

      uses ncs:service-data;
      ncs:servicepoint "empty-service";

      leaf name {
        type string;
      }

      leaf str-value {
        type string;
      }
    }
  }
}
