module java-service {
  namespace "http://com/example/javaservice";
  prefix java-service;

  import ietf-inet-types {
    prefix inet;
  }
  import tailf-common {
    prefix tailf;
  }
  import tailf-ncs {
    prefix ncs;
  }

  container java-service {
   tailf:action action {
      tailf:actionpoint action-action;
      output {
        leaf success {
          type boolean;
        }
        leaf message {
          type string;
          description
            "Free format message.";
        }
      }
    }
    list service {
      description "Parameterized Java based service";

      key name;
      leaf name {
        tailf:info "Unique service id";
        tailf:cli-allow-range;
        type string;
      }

      uses ncs:service-data;
      ncs:servicepoint java-service-servicepoint;

      leaf delay {
        type uint16;
        default 0;
      }

      leaf str-value {
        type string;
      }
    }
  }
}
