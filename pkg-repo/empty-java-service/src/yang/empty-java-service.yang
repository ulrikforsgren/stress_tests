module empty-java-service {
  namespace "http://com/example/emptyjavaservice";
  prefix empty-java-service;

  import ietf-inet-types {
    prefix inet;
  }
  import tailf-common {
    prefix tailf;
  }
  import tailf-ncs {
    prefix ncs;
  }

  container empty-java-service {
    list service {
      description "Java based service with an empty create method";

      key name;
      leaf name {
        tailf:info "Unique service id";
        tailf:cli-allow-range;
        type string;
      }

      uses ncs:service-data;
      ncs:servicepoint empty-java-service-servicepoint;

      leaf delay {
        type uint16;
        default 0;
      }

      leaf str-value {
        type string;
      }
    }
  }
}
