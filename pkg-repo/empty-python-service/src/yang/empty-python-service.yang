module empty-python-service {

  namespace "http://example.com/empty-python-service";
  prefix empty-python-service;

  import ietf-inet-types {
    prefix inet;
  }
  import tailf-common {
    prefix tailf;
  }
  import tailf-ncs {
    prefix ncs;
  }

  description
    "Python service with an empty create method";

  revision 2016-01-01 {
    description
      "Initial revision.";
  }

  container empty-python-service {
    list service {
      key name;
      leaf name {
        tailf:info "Unique service id";
        tailf:cli-allow-range;
        type string;
      }

      uses ncs:service-data;
      ncs:servicepoint empty-python-service-servicepoint;

      leaf delay {
        type uint16;
        default 0;
      }

      leaf str-value {
        type string;
      }
    }
  }
}
