module python-service {

  namespace "http://example.com/python-service";
  prefix python-service;

  import ietf-inet-types {
    prefix inet;
  }
  import tailf-common {
    prefix tailf;
  }
  import tailf-ncs {
    prefix ncs;
  }

  description
    "Parameterized Python based service";

  revision 2016-01-01 {
    description
      "Initial revision.";
  }

  container python-service {
    list service {
      key name;
      leaf name {
        tailf:info "Unique service id";
        tailf:cli-allow-range;
        type string;
      }

      uses ncs:service-data;
      ncs:servicepoint python-service-servicepoint;

      leaf delay {
        type uint16;
        default 0;
      }

      leaf device {
        type string;
      }

      leaf str-value {
        type string;
      }

      leaf start-vlan {
        type uint16;
        default 1;
      }

      leaf num-vlan {
        type uint16;
        default 0;
      }

      leaf-list template {
        type string;
      }
    }
  }
}
