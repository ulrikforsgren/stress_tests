module model-a {
  namespace "http://com/example/modela";
  prefix model-a;

  container model-a {
    list list {
      key name;

      leaf name {
        type string;
      }

      leaf str-value {
        type string;
      }
    }
  }
}
